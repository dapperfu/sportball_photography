[DOCUMENT]
TITLE: No Sidecar I/O
UID: DOC-NO-SIDECAR-001
VERSION: 1.0
DATE: 2026-09-19

[GRAMMAR]
ELEMENTS:
- TAG: REQUIREMENT
  FIELDS:
  - TITLE: UID
    TYPE: String
    REQUIRED: True
  - TITLE: TITLE
    TYPE: String
    REQUIRED: True
  - TITLE: STATEMENT
    TYPE: String
    REQUIRED: True
  - TITLE: RATIONALE
    TYPE: String
    REQUIRED: False
  - TITLE: COMMENT
    TYPE: String
    REQUIRED: False
  - TITLE: PRIORITY
    TYPE: String
    REQUIRED: False
  - TITLE: STATUS
    TYPE: String
    REQUIRED: False

[REQUIREMENT]
UID: NS-001
TITLE: Game Split Only
STATEMENT: Sportball SHALL organize photos into game folders using EXIF capture times. It SHALL NOT read or write sidecar files (.scar, .json, .bin, .rkyv, or any other sidecar extension) for game detection, animation, or any other operation.
RATIONALE: This package exists to split a dump of sports photos into game folders. Metadata files are out of scope.
PRIORITY: Critical
STATUS: Implemented

[REQUIREMENT]
UID: NS-002
TITLE: No sidecar-rs Dependency
STATEMENT: Sportball SHALL NOT depend on sidecar-rs, image-sidecar-rust, or any other sidecar manager.
RATIONALE: Sidecar tooling is a separate concern and is not required to split games.
PRIORITY: Critical
STATUS: Implemented

[REQUIREMENT]
UID: NS-003
TITLE: In-Memory Results
STATEMENT: Detection results SHALL remain in memory or be shown on the CLI. Sportball SHALL NOT write game_detection.json or per-image sidecar documents.
RATIONALE: Game split output is folders of photos (symlinks or copies), not metadata files.
PRIORITY: Critical
STATUS: Implemented
